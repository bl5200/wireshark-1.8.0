-- $Id: MAP-Group-Call-Operations.asn 39386 2011-10-12 16:41:42Z etxrab $
-- 3GPP TS 29.002 V10.4.0 (2011-09)  
-- 17.6.7	Group Call operations
 
MAP-Group-Call-Operations {
   itu-t identified-organization (4) etsi (0) mobileDomain (0)
   gsm-Network (1) modules (3) map-Group-Call-Operations (22)
   version13 (13)}

DEFINITIONS

::=

BEGIN

EXPORTS
	prepareGroupCall,
	sendGroupCallEndSignal,
	forwardGroupCallSignalling,
	processGroupCallSignalling,
	sendGroupCallInfo
;

IMPORTS
	OPERATION
FROM Remote-Operations-Information-Objects {
joint-iso-itu-t remote-operations(4)
  informationObjects(5) version1(0)}

	systemFailure,
	unexpectedDataValue,
	noGroupCallNumberAvailable,
	ongoingGroupCall,
	unknownSubscriber,
	teleserviceNotProvisioned,
	dataMissing
FROM MAP-Errors {
   itu-t identified-organization (4) etsi (0) mobileDomain (0)
   gsm-Network (1) modules (3) map-Errors (10) version13 (13)}

	PrepareGroupCallArg,
	PrepareGroupCallRes,
	SendGroupCallEndSignalArg,
	SendGroupCallEndSignalRes,
	ForwardGroupCallSignallingArg,
	ProcessGroupCallSignallingArg,
	SendGroupCallInfoArg,
	SendGroupCallInfoRes
FROM MAP-GR-DataTypes {
   itu-t identified-organization (4) etsi (0) mobileDomain (0)
   gsm-Network (1) modules (3) map-GR-DataTypes (23) version13 (13)}

;

prepareGroupCall  OPERATION ::= {				--Timer m
	ARGUMENT
		PrepareGroupCallArg
	RESULT
	PrepareGroupCallRes
	ERRORS {
		systemFailure |
		noGroupCallNumberAvailable |
		unexpectedDataValue}
	CODE	local:39 }

sendGroupCallEndSignal  OPERATION ::= {				--Timer l
	ARGUMENT
		SendGroupCallEndSignalArg
	RESULT
		SendGroupCallEndSignalRes
	CODE	local:40 }

processGroupCallSignalling  OPERATION ::= {				--Timer s
	ARGUMENT
		ProcessGroupCallSignallingArg
	CODE	local:41 }

forwardGroupCallSignalling  OPERATION ::= {				--Timer s
	ARGUMENT
		ForwardGroupCallSignallingArg
	CODE	local:42 }

sendGroupCallInfo  OPERATION ::= {				--Timer m
	ARGUMENT
		SendGroupCallInfoArg
	RESULT
		SendGroupCallInfoRes
	ERRORS {
		systemFailure |
		ongoingGroupCall |
		unexpectedDataValue |
		dataMissing |
		teleserviceNotProvisioned |
		unknownSubscriber}
	CODE	local:84 }


END
