-- 3GPP TS 36.331 V10.5.0 (2012-03)﻿
-- $Id: EUTRA-InterNodeDefinitions.asn 41917 2012-04-04 07:47:54Z etxrab $
--
EUTRA-InterNodeDefinitions DEFINITIONS AUTOMATIC TAGS ::=

BEGIN

IMPORTS
	AntennaInfoCommon,
	CellIdentity,
	C-RNTI,
	DL-DCCH-Message,
	ARFCN-ValueEUTRA,
	MasterInformationBlock,
	maxFreq,
	MeasConfig,
	OtherConfig-r9,
	PhysCellId,
	RadioResourceConfigDedicated,
	RSRP-Range,
	RSRQ-Range,
	SCellToAddModList-r10,
	SecurityAlgorithmConfig,
	ShortMAC-I,
	SystemInformationBlockType1,
	SystemInformationBlockType1-v890-IEs,
	SystemInformationBlockType2,
	UECapabilityInformation,
	UE-CapabilityRAT-ContainerList
FROM EUTRA-RRC-Definitions;


HandoverCommand ::=					SEQUENCE {
	criticalExtensions					CHOICE {
		c1									CHOICE{
			handoverCommand-r8					HandoverCommand-r8-IEs,
			spare7 NULL,
			spare6 NULL, spare5 NULL, spare4 NULL,
			spare3 NULL, spare2 NULL, spare1 NULL
		},
		criticalExtensionsFuture			SEQUENCE {}
	}
}

HandoverCommand-r8-IEs ::=			SEQUENCE {
	handoverCommandMessage				OCTET STRING (CONTAINING DL-DCCH-Message),
	nonCriticalExtension				SEQUENCE {}							OPTIONAL
}


HandoverPreparationInformation ::=	SEQUENCE {
	criticalExtensions					CHOICE {
		c1									CHOICE{
			handoverPreparationInformation-r8	HandoverPreparationInformation-r8-IEs,
			spare7 NULL,
			spare6 NULL, spare5 NULL, spare4 NULL,
			spare3 NULL, spare2 NULL, spare1 NULL
		},
		criticalExtensionsFuture			SEQUENCE {}
	}
}

HandoverPreparationInformation-r8-IEs ::= SEQUENCE {
	ue-RadioAccessCapabilityInfo		UE-CapabilityRAT-ContainerList,
	as-Config							AS-Config					OPTIONAL, 		-- Cond HO
	rrm-Config							RRM-Config					OPTIONAL,
	as-Context							AS-Context				OPTIONAL, 		-- Cond HO
	nonCriticalExtension				HandoverPreparationInformation-v920-IEs		OPTIONAL
}

HandoverPreparationInformation-v920-IEs	::= SEQUENCE {
	ue-ConfigRelease-r9					ENUMERATED {
										rel9, rel10, spare6, spare5, spare4, spare3,
										spare2, spare1, ...} 			OPTIONAL, 	-- Cond HO2
	nonCriticalExtension				SEQUENCE {}						OPTIONAL
}


UERadioAccessCapabilityInformation ::= SEQUENCE {
	criticalExtensions					CHOICE {
		c1									CHOICE{
			ueRadioAccessCapabilityInformation-r8
												UERadioAccessCapabilityInformation-r8-IEs,
			spare7 NULL,
			spare6 NULL, spare5 NULL, spare4 NULL,
			spare3 NULL, spare2 NULL, spare1 NULL
		},
		criticalExtensionsFuture			SEQUENCE {}
	}
}

UERadioAccessCapabilityInformation-r8-IEs ::= SEQUENCE {
	ue-RadioAccessCapabilityInfo		OCTET STRING (CONTAINING UECapabilityInformation),
	nonCriticalExtension				SEQUENCE {}							OPTIONAL
}


AS-Config ::=				SEQUENCE {
	sourceMeasConfig					MeasConfig,
	sourceRadioResourceConfig			RadioResourceConfigDedicated,
	sourceSecurityAlgorithmConfig		SecurityAlgorithmConfig,
	sourceUE-Identity					C-RNTI,
	sourceMasterInformationBlock		MasterInformationBlock,
	sourceSystemInformationBlockType1	SystemInformationBlockType1(WITH COMPONENTS
											{..., nonCriticalExtension ABSENT}),
	sourceSystemInformationBlockType2	SystemInformationBlockType2,
	antennaInfoCommon					AntennaInfoCommon,
	sourceDl-CarrierFreq				ARFCN-ValueEUTRA,
	...,
	[[	sourceSystemInformationBlockType1Ext	OCTET STRING (CONTAINING
												SystemInformationBlockType1-v890-IEs)	OPTIONAL,
		sourceOtherConfig-r9				OtherConfig-r9
	]],
	[[	sourceSCellConfigList-r10			SCellToAddModList-r10			OPTIONAL
	]]
}


AS-Context ::=							SEQUENCE {
	reestablishmentInfo						ReestablishmentInfo			OPTIONAL	-- Cond HO
}


ReestablishmentInfo ::=				SEQUENCE {
	sourcePhysCellId					PhysCellId,
	targetCellShortMAC-I				ShortMAC-I,
	additionalReestabInfoList			AdditionalReestabInfoList				OPTIONAL,
	...
}

AdditionalReestabInfoList ::=		SEQUENCE ( SIZE (1..maxReestabInfo) ) OF AdditionalReestabInfo

AdditionalReestabInfo ::=	SEQUENCE{
	cellIdentity						CellIdentity,
	key-eNodeB-Star					Key-eNodeB-Star,
	shortMAC-I							ShortMAC-I
}

Key-eNodeB-Star ::=					BIT STRING (SIZE (256))


RRM-Config ::=				SEQUENCE {
	ue-InactiveTime				ENUMERATED {
									s1, s2, s3, s5, s7, s10, s15, s20,
									s25, s30, s40, s50, min1, min1s20c, min1s40,
									min2, min2s30, min3, min3s30, min4, min5, min6,
									min7, min8, min9, min10, min12, min14, min17, min20,
									min24, min28, min33, min38, min44, min50, hr1,
									hr1min30, hr2, hr2min30, hr3, hr3min30, hr4, hr5, hr6,
									hr8, hr10, hr13, hr16, hr20, day1, day1hr12, day2,
									day2hr12, day3, day4, day5, day7, day10, day14, day19,
									day24, day30, dayMoreThan30}		OPTIONAL,
	...,
	[[	candidateCellInfoList-r10	CandidateCellInfoList-r10		OPTIONAL
	]]
}

CandidateCellInfoList-r10 ::=	SEQUENCE (SIZE (1..maxFreq)) OF CandidateCellInfo-r10

CandidateCellInfo-r10 ::=		SEQUENCE {
	-- cellIdentification
	physCellId-r10					PhysCellId,
	dl-CarrierFreq-r10				ARFCN-ValueEUTRA,
	-- available measurement results
	rsrpResult-r10					RSRP-Range			OPTIONAL,
	rsrqResult-r10					RSRQ-Range			OPTIONAL,
	...
}


maxReestabInfo				INTEGER ::= 32	-- Maximum number of KeNB* and shortMAC-I forwarded
											-- at handover for re-establishment preparation


END
